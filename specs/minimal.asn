Minimal DEFINITIONS AUTOMATIC TAGS ::= BEGIN

-- Basic types
Boolean ::= INTEGER (0..1)
Int8U ::= INTEGER (0..255)
Int16U ::= INTEGER (0..65535)
Int32U ::= INTEGER (0..4294967295)
Int16 ::= INTEGER (-32768..32767)
Int32 ::= INTEGER (-2147483648..2147483647)

-- OCTET STRING
OctetString ::= OCTET STRING
Float32 ::= OCTET STRING (SIZE (4))
UtcTime ::= OCTET STRING (SIZE(8))
BinaryTime ::= OCTET STRING (SIZE(6))

-- BIT STRING with named bits
TimeQuality ::= BIT STRING {
    leap-second-known            (0),
    clock-failure                (1),
    clock-not-synchronized       (2)
} (SIZE(8))

-- INTEGER with named values
ServiceError ::= INTEGER {
    no-error                    (0),
    access-violation            (3),
    type-conflict               (10)
} (0..12)

Originator ::= SEQUENCE {
    orCat        INTEGER {
        notSupported      (0),
        bayControl        (1),
        stationControl    (2)
    } (0..8),
    orIdent      OCTET STRING (SIZE(0..64))
}

-- CHOICE
Data ::= CHOICE {
    boolean            [3] IMPLICIT BOOLEAN,
    int8u              [8] IMPLICIT Int8U,
    int16u             [9] IMPLICIT Int16U,
    int32u             [10] IMPLICIT Int32U,
    float32            [12] IMPLICIT Float32,
    octet-string       [15] IMPLICIT OCTET STRING,
    utc-time           [18] IMPLICIT UtcTime,
    binary-time        [19] IMPLICIT BinaryTime
}

-- SEQUENCE
Apch ::= SEQUENCE {
    cc  Int8U,
    fl  Int16U
}

-- SEQUENCE with DEFAULT
GetDataValues-ResponsePDU ::= SEQUENCE {
    value            SEQUENCE OF Data,
    moreFollows      BOOLEAN DEFAULT TRUE
}

Apdu ::= SEQUENCE {
    apch Apch,
    asdu OCTET STRING (SIZE(0..65535))
}

END
